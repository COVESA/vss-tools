part def A {

	// sensor: A sensor.
	// unit: km
	singleLineNotQuoted : ScalarValues::Real;

	// sensor: A sensor.
	// unit: km
	singleLineInternalQuotes : ScalarValues::Real;

	// sensor: A sensor.
	// unit: km
	singleLineQuoted : ScalarValues::Real;

	// sensor: A sensor.
	// unit: km
	singleLineQuotedInternalQuotes : ScalarValues::Real;

	// sensor: A sensor.
	// unit: km
	singleLineComma : ScalarValues::Real;

	// sensor: A sensor.
	// unit: km
	singleLineCommaQuoted : ScalarValues::Real;

	// sensor: A sensor.
	// unit: km
	multiLineCommaNotQuoted : ScalarValues::Real;

	// sensor: A sensor.
	// unit: km
	multiLineCommaQuoted : ScalarValues::Real;

	// sensor: A sensor.
	// unit: km
	multiLineStyleInitialBreak : ScalarValues::Real;

	// sensor: A sensor.
	// unit: km
	multiLineLiteralStyleQuote : ScalarValues::Real;
}
