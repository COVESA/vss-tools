part def A {

	// sensor: A uint8.
	// unit: km
	uInt8 : ScalarValues::Integer;

	// sensor: An int8.
	// unit: km
	int8 : ScalarValues::Integer;

	// sensor: A uint16.
	// unit: km
	uInt16 : ScalarValues::Integer;

	// sensor: An int16.
	// unit: km
	int16 : ScalarValues::Integer;

	// sensor: A uint32.
	// unit: km
	uInt32 : ScalarValues::Integer;

	// sensor: An int32
	// unit: km
	int32 : ScalarValues::Integer;

	// sensor: A uint64.
	// unit: km
	uInt64 : uint64;

	// sensor: An int64
	// unit: km
	int64 : int64;

	// sensor: A boolean
	isBoolean : ScalarValues::Boolean;

	// sensor: A float.
	// unit: km
	float : ScalarValues::Real;

	// sensor: A double.
	// unit: km
	double : double;
}
