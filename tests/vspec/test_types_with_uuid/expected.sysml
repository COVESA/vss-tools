part def A {

	// sensor: A sensor.
	// unit: km
	sensor : ScalarValues::Real;

	// sensor: An attribute.
	// unit: km
	attribute : ScalarValues::Real;

	// sensor: An actuator.
	// unit: km
	actuator : ScalarValues::Real;
}
